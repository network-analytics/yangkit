module insa-test-dependence {
  yang-version 1.1;
  namespace "urn:ietf:params:xml:ns:yang:insa-testfd";
  prefix itdy;

  import insa-test {
    prefix ity;
    reference "None";
  }

  organization "INSA Lyon";

  description
    "insa-test YANG module.";

  revision 2023-09-05 {
    description "Initial version.";
  }

    augment "/ity:insa-container" {
        leaf addrewsssss {
            type string;
            description "address";
        }
    }
}
