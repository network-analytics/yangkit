module insa-test {
  yang-version 1.1;
  namespace "urn:ietf:params:xml:ns:yang:insa-test";
  prefix ity;

  organization "INSA Lyon";
  description
    "insa-test YANG module.";

  revision 2023-09-05 {
    description "Initial version.";
  }

  container insa-container {
    config false;
    leaf computer {
      type string;
      mandatory true;
      description "computer";
    }
    leaf router {
      type uint8;
      description "router";
    }
  }

  augment "/ity:insa-container" {
    leaf address {
      type string;
      mandatory true;
      description "address";
    }
  }
}
